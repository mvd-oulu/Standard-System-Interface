package the_sample_model {
    package part_definition {}
    package port_definition {}
    package interface_definition {}
    package connection_definition {}
   // package attrbute_deffinition {}
}
