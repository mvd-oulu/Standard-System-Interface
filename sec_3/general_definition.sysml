package general_definition{
    part def part_1 {
        attribute attr_1;
        attribute attr_2;
        }
    part def part_2{
        attribute attr_3;
        attribute attr_4;
        }
    
    item def item_1{
        attribute attr_5;
        attribute attr_6;
        }
    item def item_2{
        attribute attr_7;
        attribute attr_8;
        }  
}
